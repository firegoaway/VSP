(defun C:4OFF ( / pl1 pl2)
  ;;;??????????? 2 ?????????
  (vl-load-com)
(setq pl1 (mip:entsel "\n???????? 1-? ?????????: " '("LWPOLYLINE" "POLYLINE") nil))
(redraw pl1 3) 
(setq pl2 (mip:entsel "\n???????? 2-? ?????????: " '("LWPOLYLINE" "POLYLINE") (list pl1)))
((lambda (p1s p1e p2s p2e / p1 p2 p3 p4)
   (if (< (distance p1s p2s)(distance p1s p2e))
     (setq p1 p1s p2 p2s)
     (setq p1 p1s p2 p2e)
     )
   (if (< (distance p1e p2e)(distance p1e p2s))
     (setq p3 p1e p4 p2e)
     (setq p3 p1e p4 p2s)
     )
   (setq e1 (Line p1 p2))
   (setq e2 (Line p3 p4))
(if (and (getvar "PEDITACCEPT") (= (getvar "PEDITACCEPT") 1))
  (if command-s
    (command-s "_pedit" "_Multiple" pl1 pl2 e1 e2 "" "_Join" 0 "")
    (vl-cmdf "_pedit" "_Multiple" pl1 pl2 e1 e2 "" "_Join" 0 "")
    )
  (if command-s
    (command-s "_pedit" "_Multiple" pl1 pl2 e1 e2 "" "_Y" "_Join" 0 "")
    (vl-cmdf "_pedit" "_Multiple" pl1 pl2 e1 e2 "" "_Y" "_Join" 0 "")
    )
  )
   (if (setq e1 (car (vl-remove-if '(lambda(x)(null(entget x))) (list pl1 pl2 e1 e2 (entlast)))))
   (if command-s
    (command-s "_ZOOM" "_O" e1 "")
    (vl-cmdf "_ZOOM" "_O" e1 "")
    )
     )
   (sssetfirst (ssadd (entlast))(ssadd (entlast)))
   )
  (vlax-curve-getStartPoint pl1)
  (vlax-curve-getEndPoint pl1)
  (vlax-curve-getStartPoint pl2)
  (vlax-curve-getEndPoint pl2)
  )
  (princ)
)
(defun Line (p1 p2)
  (entmakex (list (cons 0 "LINE")
                  (cons 10 p1)
                  (cons 11 p2))))
(defun mip:entsel (promt filter entlist / key n newentlist ent_point promt)

;;;??????? mip:entsel
;;;????????? ????? ???????, ?????? ??????? entsel
;;;?????????? entity name ?????????? ????????? ??? nil, ????? ???????? ?????????? ? ?????????? LASTPOINT
;;;?????????:
;;;promt - ??????????? ??????? ?????? (string)
;;;filter - ?????? ???????? ??? ?????? ???? '("LINE" "LWPOLYLINE")
;;;entlist - ?????? ?????????? ??????? ?? ???? ???????? (???? ?????? entity name, ???? PICKSET)
;;;
;;;???????:
;;;(mip:entsel "\n???????? ???????" '("LINE" "LWPOLYLINE") nil)
;;;(mip:entsel "\n???????? ???????" nil nil)
;;;(setq aa nil) (mip:entsel "\n???????? ???????" '("LINE" "LWPOLYLINE") (while (setq a (car (entsel))) (setq aa (append aa (list a)))))
;;;(mip:entsel "\n???????? ???????" '("LINE" "LWPOLYLINE") (ssget))
  (setq key T n 0 newentlist nil)
  (if (eq (type entlist) 'PICKSET)
    (progn
    	(while (setq a (ssname entlist n)) (setq newentlist (append newentlist (list a)) n (1+ n)))
    	(setq entlist newentlist)
    );progn
   );if
    (while key
    	(if (or (setq ent_point (entsel promt)) (= (getvar "ERRNO") 7))
	  	(if (or (eq (type ent_point) 'LIST) (not ent_point))
		  (if ent_point
		    (if (member (setq ent (car ent_point)) entlist)
		      (princ "\n???????? ??? ??????")
		      (if filter
			      (if (not (member (cdr (assoc 0 (entget ent))) filter))
				(progn (setq str "\n?? ?????? ?????, ????????: ")
				  (princ (substr (setq str (foreach n filter (setq str (strcat str n ", ")))) 1 (- (strlen str) 2)))
				);progn
				(setq key nil)
			      );if
				(setq key nil)
			);if
		    );if
		    (setq key T)
		  );if
	    	(setq key nil)
	    );if
	  (setq key nil)
      	);if
     );while
  (if (eq (type ent_point) 'LIST)
    (progn (setvar "LASTPOINT" (cadr ent_point)) ent)
    ent_point
  );if
)
